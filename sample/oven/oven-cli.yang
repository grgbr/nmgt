module oven-cli {
	yang-version 1.1;
	namespace "urn:sysrepo:oven-cli";
	prefix ov-cli;

	import oven {
		prefix ov;
	}

	import cli-extensions {
		prefix cli-ext;
	}

	revision 2026-08-06 {
		description "Initial revision.";
	}

	augment "/cli-ext:services" {
		container oven {
			description "Command line oven menu directory entry.";
		}
	}

	augment "/ov:oven" {
		cli-ext:menu {
			//cli-ext:ignore;
			path "/cli-ext:services/ov-cli:oven";
			cli-ext:show-config-command "config" {
				description "Shows oven configuration settings.";
			}
		}
	}

	augment "/ov:oven-state" {
		cli-ext:menu {
			//cli-ext:ignore;
			path "/cli-ext:services/ov-cli:oven";
			cli-ext:show-state-command "status" {
				description "Shows oven operational state.";
			}
		}
	}
}
