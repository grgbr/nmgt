/******************************************************************************
 * Command line YANG extensions.
 *
 * For inspiration, see:
 * <openconfig-public>/release/models/openconfig-extensions.yang
 ******************************************************************************/

module cli-extensions {
	yang-version 1.1;
	namespace "urn:cli:yang:cli-extensions";
	prefix cli-ext;

	description "This module provides command line specific extensions to
                     the YANG language.";

	revision 2026-08-04 {
		description "Initial revision.";
	}

	/*
	 * Extension definitions.
	 */

	extension menu {
		description "When specified, this extension directive instructs
                             the command line shell to attach subsequent command
                             instantiations to the menu directory entry
			     identified by the path argument.";
	}

	extension ignore {
		description "When specified, this extension directive instructs
                             the command line shell to ignore all menu and
                             command directives attached to the current
                             container.";
	}

	extension show-config-command {
		argument "name" {
			yin-element false;
		}

		description "When specified, this extension directive instructs
			     the command line shell to instantiate a command
                             identified by the name given in argument that shows
                             configuration informations.";

	}

	extension show-state-command {
		argument "name" {
			yin-element false;
		}

		description "When specified, this extension directive instructs
			     the command line shell to instantiate a command
                             identified by the name given in argument that shows
                             operational state informations.";
	}

	extension edit-config-command {
		argument "name" {
			yin-element false;
		}

		description "When specified, this extension directive instructs
			     the command line shell to instantiate a command
                             identified by the name given in argument that
                             modifies configuration settings.";
	}


	/*
	 * Top-level menu directory entry definitions.
	 */

	container services {
		description "Top-level command line services menu directory
                             entry.";
	}
}
